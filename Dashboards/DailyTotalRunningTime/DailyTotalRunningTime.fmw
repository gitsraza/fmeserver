FME workspace DailyTotalRunningTime.fmw

Parameters:
- Output = $(FME_SHAREDRESOURCE_DASHBOARD)/dashboards/DailyTotalRunningTime.html   # HTML Output Location
- Input_2 = $(FME_SHAREDRESOURCE_DASHBOARD)/temp   # CSV Location

Readers:
- PATH_1: PATH from $(Input_2)

Writers:
- HTML_1: HTML to $(Output)

Bookmark: Read Data
PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> Sorter_2
Sorter_2
    SORT_PARM = path_rootname ALPHA DESCENDING
    SORTED -> FeatureReader [INITIATOR]
FeatureReader
    ATTRIBUTES = CSV,"timeFinished,timeStarted,status,statusMessage,timeQueued,timeDelivered,timeSubmitted,description,numFeaturesOutput,WorkspaceName,Repository,JobStatus"
    ATTR_ACCUM_MODE = Only Use Result
    COMBINE_GEOM = Use Result
    CSV2_CASE_SENSITIVE_FIELD_NAMES = Yes
    CSV2_DATA_START_LINE = 2
    CSV2_DELIMITER = ,
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = @Value(path_windows)
    FORMAT = CSV2
    INTERACT = NONE
    OUTPUT_FEATURES_DISPLAY = Schema and Data Features
    CSV -> DuplicateFilter
DuplicateFilter
    INPUT_ORDERED_CHOICE = No
    KEYATTR = WorkspaceName Repository timeStarted timeSubmitted timeDelivered JobStatus numFeaturesOutput status description timeFinished statusMessage timeQueued
    UNIQUE -> Tester_2

Bookmark: Calculate Daily Total Running Time
Note: Filter out any jobs that were cancelled / before they started running.
Tester_2
    BOOL_OP = OR
    TEST_CLAUSE = TEST timeStarted NOT_ATTRIBUTE_IS_EMPTY ""
    TEST_MODE = TEST
    PASSED -> AttributeCopier
    FAILED -> Tester_2_Failed
Tester_2_Failed: Logger
    LOG_FEATURE = LOG_RECORD
    MAXCOORDS = 20
    MAXFEATS = 20
    MESSAGE = Feature is:
    SEVERITY = INFO

Bookmark: Calculate runtime per job
AttributeCopier
    ATTR_TABLE:
      COPY timeFinished > _timeFinishedEpoch
      COPY timeStarted > _timeStartedEpoch
    MISSING_INPUT_ATTRS = PRESERVE
    -> DateFormatter
DateFormatter
    DATE_ATTR = _timeStartedEpoch,_timeFinishedEpoch
    FMT = %s
    INVALID_DATE_VALUE = _FME_NO_OP_
    SRCFMT = %Y-%m-%dT%H:%M:%S
    -> AttributeCreator_2
AttributeCreator_2
    ATTR_TABLE:
      SET_TO RunTime = @Evaluate(@Value(_timeFinishedEpoch)-@Value(_timeStartedEpoch))
      SET_TO Date = @Value(timeFinished)
    -> DateFormatter_2

Bookmark: Get Total Run Time
DateFormatter_2
    DATE_ATTR = Date
    FMT = FME Date (%Y%m%d)
    INVALID_DATE_VALUE = _FME_NO_OP_
    SRCFMT = %Y-%m-%dT%H:%M:%S
    -> Aggregator
Aggregator
    ACCUM_ATTRS_NAME = Drop Incoming Attributes
    GROUP_BY = Date
    MODE = Attributes Only
    SEP = ,
    SUM = RunTime
    AGGREGATE -> Sorter

Bookmark: Daily Total Running Time
Sorter
    SORT_PARM = Date NUMERIC ASCENDING
    SORTED -> DateFormatter_3
DateFormatter_3
    DATE_ATTR = Date
    FMT = %b %e %Y
    INVALID_DATE_VALUE = _FME_NO_OP_
    SRCFMT = %Y%m%d
    -> HTMLReportGenerator

Bookmark: Create HTML Report
HTMLReportGenerator
    CONTENT_LIST = HEADER HEADER CHART_LINE
    PAGE_CONFIG = HEADER{{TEXT;Daily Total Running Time;HEADER;H1;HEADER_ID;;ALIGNMENT;CENTER;COLOR;0,0,0;FME_CONTROLLER_QUERY_FILE;transformers/dependencies/html5/Header.fme;FME_CONTROLLER_CHOICE;Header}}HEADER{{TEXT;Total Time (in Seconds) FME Server Engines have Spent Running Jobs;HEADER;H3;HEADER_ID;;ALIGNMENT;CENTER;COLOR;102,102,102;FME_CONTROLLER_QUERY_FILE;transformers/dependencies/html5/Header.fme;FME_CONTROLLER_CHOICE;Header}}CHART_LINE{{X_LABEL;;r;Date;Y_LABEL;Running Time in Seconds;TABLE;RunTime|0,0,255;FME_CONTROLLER_QUERY_FILE;transformers/dependencies/html5/Chart (Line).fme;FME_CONTROLLER_CHOICE;Chart (Line)}}
    TITLE = Daily Total Running Time
    -> StringReplacer_3
HTML (writer HTML_1)
    attributes: html_content buffer

Bookmark: Style adjustments for output html file
StringReplacer_3
    CASE = NO
    FIND_TEXT = col-xs-8
    NO_MATCH = _FME_NO_OP_
    REGEXP = NO
    REPLACE_TEXT = col-xs-12
    SRC_ATTRS = html_content
    -> StringReplacer_4
StringReplacer_4
    CASE = NO
    FIND_TEXT = col-xs-4
    NO_MATCH = _FME_NO_OP_
    REGEXP = NO
    REPLACE_TEXT = col-xs-2
    SRC_ATTRS = html_content
    -> AttributeCreator
AttributeCreator
    ATTR_TABLE:
      SET_TO _bootstrap_min_css =      <style>
              /*!
         * Bootstrap v3.3.4 (http://getbootstrap.com)
         * Copyright 2011-2015 Twitter, Inc.
         * Licensed under MIT (https://github.com/twbs/bootstrap/blob/master/LICENSE)
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              </style>
      SET_TO _chartjs_min_js = <script>
        /*!
         * Chart.js
         * http://chartjs.org/
         * Version: 2.7.2
         *
         * Copyright 2018 Chart.js Contributors
         * Released under the MIT license
         * https://github.com/chartjs/Chart.js/blob/master/LICENSE.md
         */
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        </script>
      SET_TO _server_min_css =       <style>
              #body ol li,#body ul li{margin-left:35px;display:list-item}#body ol,#body ul,h2,h3{margin:20px 0}h1,h2,h3{word-break:normal}a:focus,a:hover{text-decoration:none}*,.inline-block,.x-btn .glyphicon,button .glyphicon,td{vertical-align:middle}*,:after,:before{-webkit-box-sizing:border-box;-moz-box-sizing:border-box;box-sizing:border-box}html{height:100%}body{position:relative;margin:0;min-height:100%;overflow-y:scroll}body.modal-open{overflow-y:scroll;position:fixed;width:100%}body *{font-family:Lato,sans-serif}#body ul li{list-style-type:disc}#body ol li{list-style-type:decimal}label,p{font-family:Oxygen,sans-serif;margin-bottom:8px}footer{position:absolute;right:0;bottom:0;left:0;font-size:12px}:focus{outline:0!important;box-shadow:none!important}td{display:table-cell}table.noPad tr{border:0!important}table.noPad td{padding:0!important}button,input[type=email],input[type=number],input[type=password],input[type=text],select,textarea{-webkit-appearance:none;-moz-appearance:none;border-radius:6px;border:2px solid #d6d6d6;color:#797979;padding:8px;margin-bottom:35px;background-color:#FFF;min-height:40px}textarea{min-height:125px;resize:vertical}.ng-form-item{width:100%;float:left;clear:left}.ng-form-item .col-sm-9{padding-left:0;padding-right:0}input[type=checkbox],input[type=radio]{margin-bottom:8px;margin-left:15px;margin-right:5px;vertical-align:middle}input[type=email],input[type=number],input[type=password],input[type=text],select,textarea{width:100%}input[disabled],select[disabled],textarea[disabled]{opacity:.3}.btn,button{border:0;padding:11px 8px}input[type=number]:focus,input[type=password]:focus,input[type=text]:focus,select:focus,textarea:focus{border-color:#AAA}.ui-grid-pager-control button,button[disabled]{border:2px solid #78b943;background-color:#FFF;color:#78b943;padding:9px 20px;cursor:default!important}a:hover,h2{color:#7a7a7a}[data-ng-click],[ng-click],[x-ng-click],a:hover{cursor:pointer}select{background-image:url(../images/select-arrow.png)!important;background-repeat:no-repeat!important;background-size:12px 16px!important;background-position:100% 0}h1{font-size:32px;color:#333;margin:20px 0 35px}h2{font-size:22px}h3{font-size:18px}hr{border-top:1px solid #d6d6d6}a,a:visited{color:#78b943}em,i{font-style:italic}legend{border-bottom:1px solid #ececec}.breakWord{white-space:pre-wrap;word-break:break-all;word-wrap:break-word}.no-border{border:0;padding-top:17px;padding-bottom:17px}.color-red{color:#ed1c24!important}.color-green{color:#78b943!important}.color-yellow{color:#fec92e!important}.color-grey{color:#797979!important}.bg-red{background-color:#ed1c24!important}.bg-green{background-color:#78b943!important;color:#FFF!important}.bg-yellow{background-color:#fec92e!important;color:#fff!important}.bg-white{background-color:#FFF!important}.border-red,.redBorder{border-color:#ed1c24!important}.border-green{border-color:#78b943!important}.border-yellow{border-color:#fec92e!important}.badStatus{color:#ed1c24;font-size:16px}.goodStatus{color:#78b943;font-size:16px}.center{text-align:center}.current a{color:#e98300}.hidden{display:none}.float-left,.float-right,.inline-block{display:inline-block}.enabled-block{background-color:#1E7950}.disabled-block{background-color:#972900}.float-left{float:left}.float-right{float:right}.inline-block{margin-right:5px}.col-lg-1,.col-lg-10,.col-lg-11,.col-lg-12,.col-lg-2,.col-lg-3,.col-lg-4,.col-lg-5,.col-lg-6,.col-lg-7,.col-lg-8,.col-lg-9,.col-md-1,.col-md-10,.col-md-11,.col-md-12,.col-md-2,.col-md-3,.col-md-4,.col-md-5,.col-md-6,.col-md-7,.col-md-8,.col-md-9,.col-sm-1,.col-sm-10,.col-sm-11,.col-sm-12,.col-sm-2,.col-sm-3,.col-sm-4,.col-sm-5,.col-sm-6,.col-sm-7,.col-sm-8,.col-sm-9,.col-xs-1,.col-xs-10,.col-xs-11,.col-xs-12,.col-xs-2,.col-xs-3,.col-xs-4,.col-xs-5,.col-xs-6,.col-xs-7,.col-xs-8,.col-xs-9{min-height:0}.col-sm-12,.col-sm-4,.col-sm-7{padding-left:0;padding-right:0}.form-control{display:block;width:100%;height:auto;padding:8px;font-size:inherit;line-height:inherit;color:inherit;background-color:inherit;background-image:inherit;border:inherit;border-radius:inherit;-webkit-box-shadow:none;box-shadow:none;-webkit-transition:none;-o-transition:none;transition:none}.x-btn .glyphicon,button .glyphicon{line-height:normal;display:inline}.deselectAllButton.glyphicon,.selectAllButton.glyphicon{top:-2px}.navbar-nav>li>.dropdown-menu{border-bottom-left-radius:6px;border-bottom-right-radius:6px;border:1px solid #eee}.nav .open>a{border:0}.form-control-static{padding-left:15px}.form-group{margin-bottom:0}.input-group-btn{margin:0;vertical-align:top}.input-group-btn .glyphicon{top:0}.input-group-btn button,.input-group-btn button:active,.input-group-btn button:active:focus,.input-group-btn button:focus,.input-group-btn button:hover{background-color:#78b943;color:#FFF;margin-left:15px!important;border-radius:6px!important;padding:8px 20px!important}.favourites.col-sm-5.col-sm-offset-1{margin-left:7.333333%}.input-group .form-control:first-child,.input-group-addon:first-child,.input-group-btn:first-child>.btn,.input-group-btn:first-child>.btn-group>.btn,.input-group-btn:first-child>.dropdown-toggle,.input-group-btn:last-child>.btn-group:not(:last-child)>.btn,.input-group-btn:last-child>.btn:not(:last-child):not(.dropdown-toggle){border-top-right-radius:6px;border-bottom-right-radius:6px}.well{border-radius:6px;border:2px solid #d6d6d6;background-color:#FFF;box-shadow:none}.modal-body .input-group{margin-bottom:20px}.modal-body .applyMaxHeight{overflow-y:auto}.modal-body .col-sm-8.applyMaxHeight{padding-left:0}.modal-body .col-sm-4.applyMaxHeight{padding:0 15px}.modal-open footer{bottom:-50px}.buttonRow button{margin-bottom:0}.glyphicon{top:unset}.top-links{background-color:#d9d6d4;padding:5px 0}.top-links>.container>a{padding:0 10px;border-right:1px solid #aaa;font-size:16px;color:#82786f}.navigation{border-bottom:1px solid #ececec;background-color:#fff}.nav>li{border-left:1px solid #eee}.nav>li:nth-last-child(1){border-right:1px solid #eee}.nav .open a,.nav .open a:focus,.nav .open a:hover,.nav li a:hover{background:0 0}.nav li a{padding:27px 15px 24px;font-size:17px;color:#797979;border-bottom:1px solid #eee}.collapse-nav>li>a,.nav li a[data-toggle=collapse],.nav li.last a,.nav>li>a{border-bottom:0}.nav li a[data-toggle=collapse].collapsed{border-bottom:1px solid #eee}.nav.first li{border:0}.nav.first li a{padding:8px 0}.dropdown-menu li a{font-size:16px;padding:15px;display:block;color:#333}.dropdown-menu li a .glyphicon{margin-left:10px}ul.collapse-nav>li>a{color:#78b943;padding:6px 10px 6px 25px;box-shadow:none;display:block;font-size:14px;border-top:1px dashed #e5e5e5}ul.collapse-nav>li:last-of-type>a{border-bottom:1px dashed #e5e5e5}
              </style>
    -> StringReplacer
StringReplacer
    CASE = NO
    FIND_TEXT = </head>
    NO_MATCH = _FME_NO_OP_
    REGEXP = NO
    REPLACE_TEXT:
      @Value(_bootstrap_min_css)
      @Value(_server_min_css)
      @Value(_chartjs_min_js)
      </head>
    SRC_ATTRS = html_content
    -> StringReplacer_2
StringReplacer_2
    CASE = NO
    FIND_TEXT = <script src="https://cdnjs.cloudflare.com/ajax/libs/Chart.js/2.7.2/Chart.min.js"></script>
    NO_MATCH = _FME_NO_OP_
    REGEXP = NO
    SRC_ATTRS = html_content
    -> StringReplacer_5
StringReplacer_5
    CASE = NO
    FIND_TEXT = <link href="https://maxcdn.bootstrapcdn.com/bootstrap/3.3.4/css/bootstrap.min.css" rel="stylesheet">
    NO_MATCH = _FME_NO_OP_
    REGEXP = NO
    SRC_ATTRS = html_content
    -> StringReplacer_6
StringReplacer_6
    CASE = NO
    FIND_TEXT = legend: (.+?)},
    NO_MATCH = _FME_NO_OP_
    REGEXP = YES
    REPLACE_TEXT:
      legend: {
       display: false
       },
    SRC_ATTRS = html_content
    -> HTML (writer HTML_1)
